module tntapi-traffic-graphic-flows {

  namespace
    "urn:tntapi:traffic-graphic-flows";
  prefix "traffic-graphic-flows";

  import "tntapi-traffic-graphic" { prefix traffic-graphic; }
  import "ietf-network-bridge-scheduler" {prefix sched; }

  organization
    "tntapi project";

  contact
    "Vladimir Vassilev <mailto:vladimir@transpacket.com>";

  description
    "This module augments /traffic-graphic with global
     properties for representation of flows.";

  revision 2018-12-11 {
    description
      "Fixed bug by replacing the class type from leafref to identityref.";
  }

  augment "/traffic-graphic:traffic-graphic" {
    description
      "Adds container with list to configure
       properties for representation of traffic flows.";
    container traffic-classes {
      list traffic-class {
        key "class";
        leaf class {
          type identityref {
            base sched:traffic-class;
          }
        }
        leaf color {
          type string {
            pattern '[0-9A-F]{6}';
          }
        }
      }
    }
  }
}
